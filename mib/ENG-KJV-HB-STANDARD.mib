BIBLE-MIB DEFINITIONS ::= BEGIN
IMPORTS OBJECT-TYPE FROM SNMPv2-SMI;
bible OBJECT IDENTIFIER ::= { iso org(3) dod(6) internet(1) private(4) enterprises(1) 99999 }
verse0 OBJECT-TYPE
  SYNTAX OCTET STRING
  ACCESS read-only
  STATUS current
  DESCRIPTION "GEN 1:1"
  ::= { bible 1 }
verse1 OBJECT-TYPE
  SYNTAX OCTET STRING
  ACCESS read-only
  STATUS current
  DESCRIPTION "GEN 1:2"
  ::= { bible 2 }
verse2 OBJECT-TYPE
  SYNTAX OCTET STRING
  ACCESS read-only
  STATUS current
  DESCRIPTION "GEN 1:3"
  ::= { bible 3 }
verse3 OBJECT-TYPE
  SYNTAX OCTET STRING
  ACCESS read-only
  STATUS current
  DESCRIPTION "GEN 1:4"
  ::= { bible 4 }
verse4 OBJECT-TYPE
  SYNTAX OCTET STRING
  ACCESS read-only
  STATUS current
  DESCRIPTION "GEN 1:5"
  ::= { bible 5 }
verse5 OBJECT-TYPE
  SYNTAX OCTET STRING
  ACCESS read-only
  STATUS current
  DESCRIPTION "GEN 1:6"
  ::= { bible 6 }
verse6 OBJECT-TYPE
  SYNTAX OCTET STRING
  ACCESS read-only
  STATUS current
  DESCRIPTION "GEN 1:7"
  ::= { bible 7 }
verse7 OBJECT-TYPE
  SYNTAX OCTET STRING
  ACCESS read-only
  STATUS current
  DESCRIPTION "GEN 1:8"
  ::= { bible 8 }
verse8 OBJECT-TYPE
  SYNTAX OCTET STRING
  ACCESS read-only
  STATUS current
  DESCRIPTION "GEN 1:9"
  ::= { bible 9 }
verse9 OBJECT-TYPE
  SYNTAX OCTET STRING
  ACCESS read-only
  STATUS current
  DESCRIPTION "GEN 1:10"
  ::= { bible 10 }
verse10 OBJECT-TYPE
  SYNTAX OCTET STRING
  ACCESS read-only
  STATUS current
  DESCRIPTION "GEN 1:11"
  ::= { bible 11 }
verse11 OBJECT-TYPE
  SYNTAX OCTET STRING
  ACCESS read-only
  STATUS current
  DESCRIPTION "GEN 1:12"
  ::= { bible 12 }
verse12 OBJECT-TYPE
  SYNTAX OCTET STRING
  ACCESS read-only
  STATUS current
  DESCRIPTION "GEN 1:13"
  ::= { bible 13 }
verse13 OBJECT-TYPE
  SYNTAX OCTET STRING
  ACCESS read-only
  STATUS current
  DESCRIPTION "GEN 1:14"
  ::= { bible 14 }
verse14 OBJECT-TYPE
  SYNTAX OCTET STRING
  ACCESS read-only
  STATUS current
  DESCRIPTION "GEN 1:15"
  ::= { bible 15 }
verse15 OBJECT-TYPE
  SYNTAX OCTET STRING
  ACCESS read-only
  STATUS current
  DESCRIPTION "GEN 1:16"
  ::= { bible 16 }
verse16 OBJECT-TYPE
  SYNTAX OCTET STRING
  ACCESS read-only
  STATUS current
  DESCRIPTION "GEN 1:17"
  ::= { bible 17 }
verse17 OBJECT-TYPE
  SYNTAX OCTET STRING
  ACCESS read-only
  STATUS current
  DESCRIPTION "GEN 1:18"
  ::= { bible 18 }
verse18 OBJECT-TYPE
  SYNTAX OCTET STRING
  ACCESS read-only
  STATUS current
  DESCRIPTION "GEN 1:19"
  ::= { bible 19 }
verse19 OBJECT-TYPE
  SYNTAX OCTET STRING
  ACCESS read-only
  STATUS current
  DESCRIPTION "GEN 1:20"
  ::= { bible 20 }
verse20 OBJECT-TYPE
  SYNTAX OCTET STRING
  ACCESS read-only
  STATUS current
  DESCRIPTION "GEN 1:21"
  ::= { bible 21 }
verse21 OBJECT-TYPE
  SYNTAX OCTET STRING
  ACCESS read-only
  STATUS current
  DESCRIPTION "GEN 1:22"
  ::= { bible 22 }
verse22 OBJECT-TYPE
  SYNTAX OCTET STRING
  ACCESS read-only
  STATUS current
  DESCRIPTION "GEN 1:23"
  ::= { bible 23 }
verse23 OBJECT-TYPE
  SYNTAX OCTET STRING
  ACCESS read-only
  STATUS current
  DESCRIPTION "GEN 1:24"
  ::= { bible 24 }
verse24 OBJECT-TYPE
  SYNTAX OCTET STRING
  ACCESS read-only
  STATUS current
  DESCRIPTION "GEN 1:25"
  ::= { bible 25 }
verse25 OBJECT-TYPE
  SYNTAX OCTET STRING
  ACCESS read-only
  STATUS current
  DESCRIPTION "GEN 1:26"
  ::= { bible 26 }
verse26 OBJECT-TYPE
  SYNTAX OCTET STRING
  ACCESS read-only
  STATUS current
  DESCRIPTION "GEN 1:27"
  ::= { bible 27 }
verse27 OBJECT-TYPE
  SYNTAX OCTET STRING
  ACCESS read-only
  STATUS current
  DESCRIPTION "GEN 1:28"
  ::= { bible 28 }
verse28 OBJECT-TYPE
  SYNTAX OCTET STRING
  ACCESS read-only
  STATUS current
  DESCRIPTION "GEN 1:29"
  ::= { bible 29 }
verse29 OBJECT-TYPE
  SYNTAX OCTET STRING
  ACCESS read-only
  STATUS current
  DESCRIPTION "GEN 1:30"
  ::= { bible 30 }
verse30 OBJECT-TYPE
  SYNTAX OCTET STRING
  ACCESS read-only
  STATUS current
  DESCRIPTION "GEN 1:31"
  ::= { bible 31 }
verse31 OBJECT-TYPE
  SYNTAX OCTET STRING
  ACCESS read-only
  STATUS current
  DESCRIPTION "GEN 2:1"
  ::= { bible 32 }
verse32 OBJECT-TYPE
  SYNTAX OCTET STRING
  ACCESS read-only
  STATUS current
  DESCRIPTION "GEN 2:2"
  ::= { bible 33 }
verse33 OBJECT-TYPE
  SYNTAX OCTET STRING
  ACCESS read-only
  STATUS current
  DESCRIPTION "GEN 2:3"
  ::= { bible 34 }
verse34 OBJECT-TYPE
  SYNTAX OCTET STRING
  ACCESS read-only
  STATUS current
  DESCRIPTION "GEN 2:4"
  ::= { bible 35 }
verse35 OBJECT-TYPE
  SYNTAX OCTET STRING
  ACCESS read-only
  STATUS current
  DESCRIPTION "GEN 2:5"
  ::= { bible 36 }
verse36 OBJECT-TYPE
  SYNTAX OCTET STRING
  ACCESS read-only
  STATUS current
  DESCRIPTION "GEN 2:6"
  ::= { bible 37 }
verse37 OBJECT-TYPE
  SYNTAX OCTET STRING
  ACCESS read-only
  STATUS current
  DESCRIPTION "GEN 2:7"
  ::= { bible 38 }
verse38 OBJECT-TYPE
  SYNTAX OCTET STRING
  ACCESS read-only
  STATUS current
  DESCRIPTION "GEN 2:8"
  ::= { bible 39 }
verse39 OBJECT-TYPE
  SYNTAX OCTET STRING
  ACCESS read-only
  STATUS current
  DESCRIPTION "GEN 2:9"
  ::= { bible 40 }
verse40 OBJECT-TYPE
  SYNTAX OCTET STRING
  ACCESS read-only
  STATUS current
  DESCRIPTION "GEN 2:10"
  ::= { bible 41 }
verse41 OBJECT-TYPE
  SYNTAX OCTET STRING
  ACCESS read-only
  STATUS current
  DESCRIPTION "GEN 2:11"
  ::= { bible 42 }
verse42 OBJECT-TYPE
  SYNTAX OCTET STRING
  ACCESS read-only
  STATUS current
  DESCRIPTION "GEN 2:12"
  ::= { bible 43 }
verse43 OBJECT-TYPE
  SYNTAX OCTET STRING
  ACCESS read-only
  STATUS current
  DESCRIPTION "GEN 2:13"
  ::= { bible 44 }
verse44 OBJECT-TYPE
  SYNTAX OCTET STRING
  ACCESS read-only
  STATUS current
  DESCRIPTION "GEN 2:14"
  ::= { bible 45 }
verse45 OBJECT-TYPE
  SYNTAX OCTET STRING
  ACCESS read-only
  STATUS current
  DESCRIPTION "GEN 2:15"
  ::= { bible 46 }
verse46 OBJECT-TYPE
  SYNTAX OCTET STRING
  ACCESS read-only
  STATUS current
  DESCRIPTION "GEN 2:16"
  ::= { bible 47 }
verse47 OBJECT-TYPE
  SYNTAX OCTET STRING
  ACCESS read-only
  STATUS current
  DESCRIPTION "GEN 2:17"
  ::= { bible 48 }
verse48 OBJECT-TYPE
  SYNTAX OCTET STRING
  ACCESS read-only
  STATUS current
  DESCRIPTION "GEN 2:18"
  ::= { bible 49 }
verse49 OBJECT-TYPE
  SYNTAX OCTET STRING
  ACCESS read-only
  STATUS current
  DESCRIPTION "GEN 2:19"
  ::= { bible 50 }
verse50 OBJECT-TYPE
  SYNTAX OCTET STRING
  ACCESS read-only
  STATUS current
  DESCRIPTION "GEN 2:20"
  ::= { bible 51 }
verse51 OBJECT-TYPE
  SYNTAX OCTET STRING
  ACCESS read-only
  STATUS current
  DESCRIPTION "GEN 2:21"
  ::= { bible 52 }
verse52 OBJECT-TYPE
  SYNTAX OCTET STRING
  ACCESS read-only
  STATUS current
  DESCRIPTION "GEN 2:22"
  ::= { bible 53 }
verse53 OBJECT-TYPE
  SYNTAX OCTET STRING
  ACCESS read-only
  STATUS current
  DESCRIPTION "GEN 2:23"
  ::= { bible 54 }
verse54 OBJECT-TYPE
  SYNTAX OCTET STRING
  ACCESS read-only
  STATUS current
  DESCRIPTION "GEN 2:24"
  ::= { bible 55 }
verse55 OBJECT-TYPE
  SYNTAX OCTET STRING
  ACCESS read-only
  STATUS current
  DESCRIPTION "GEN 2:25"
  ::= { bible 56 }
verse56 OBJECT-TYPE
  SYNTAX OCTET STRING
  ACCESS read-only
  STATUS current
  DESCRIPTION "GEN 3:1"
  ::= { bible 57 }
verse57 OBJECT-TYPE
  SYNTAX OCTET STRING
  ACCESS read-only
  STATUS current
  DESCRIPTION "GEN 3:2"
  ::= { bible 58 }
verse58 OBJECT-TYPE
  SYNTAX OCTET STRING
  ACCESS read-only
  STATUS current
  DESCRIPTION "GEN 3:3"
  ::= { bible 59 }
verse59 OBJECT-TYPE
  SYNTAX OCTET STRING
  ACCESS read-only
  STATUS current
  DESCRIPTION "GEN 3:4"
  ::= { bible 60 }
verse60 OBJECT-TYPE
  SYNTAX OCTET STRING
  ACCESS read-only
  STATUS current
  DESCRIPTION "GEN 3:5"
  ::= { bible 61 }
verse61 OBJECT-TYPE
  SYNTAX OCTET STRING
  ACCESS read-only
  STATUS current
  DESCRIPTION "GEN 3:6"
  ::= { bible 62 }
verse62 OBJECT-TYPE
  SYNTAX OCTET STRING
  ACCESS read-only
  STATUS current
  DESCRIPTION "GEN 3:7"
  ::= { bible 63 }
verse63 OBJECT-TYPE
  SYNTAX OCTET STRING
  ACCESS read-only
  STATUS current
  DESCRIPTION "GEN 3:8"
  ::= { bible 64 }
verse64 OBJECT-TYPE
  SYNTAX OCTET STRING
  ACCESS read-only
  STATUS current
  DESCRIPTION "GEN 3:9"
  ::= { bible 65 }
verse65 OBJECT-TYPE
  SYNTAX OCTET STRING
  ACCESS read-only
  STATUS current
  DESCRIPTION "GEN 3:10"
  ::= { bible 66 }
verse66 OBJECT-TYPE
  SYNTAX OCTET STRING
  ACCESS read-only
  STATUS current
  DESCRIPTION "GEN 3:11"
  ::= { bible 67 }
verse67 OBJECT-TYPE
  SYNTAX OCTET STRING
  ACCESS read-only
  STATUS current
  DESCRIPTION "GEN 3:12"
  ::= { bible 68 }
verse68 OBJECT-TYPE
  SYNTAX OCTET STRING
  ACCESS read-only
  STATUS current
  DESCRIPTION "GEN 3:13"
  ::= { bible 69 }
verse69 OBJECT-TYPE
  SYNTAX OCTET STRING
  ACCESS read-only
  STATUS current
  DESCRIPTION "GEN 3:14"
  ::= { bible 70 }
verse70 OBJECT-TYPE
  SYNTAX OCTET STRING
  ACCESS read-only
  STATUS current
  DESCRIPTION "GEN 3:15"
  ::= { bible 71 }
verse71 OBJECT-TYPE
  SYNTAX OCTET STRING
  ACCESS read-only
  STATUS current
  DESCRIPTION "GEN 3:16"
  ::= { bible 72 }
verse72 OBJECT-TYPE
  SYNTAX OCTET STRING
  ACCESS read-only
  STATUS current
  DESCRIPTION "GEN 3:17"
  ::= { bible 73 }
verse73 OBJECT-TYPE
  SYNTAX OCTET STRING
  ACCESS read-only
  STATUS current
  DESCRIPTION "GEN 3:18"
  ::= { bible 74 }
verse74 OBJECT-TYPE
  SYNTAX OCTET STRING
  ACCESS read-only
  STATUS current
  DESCRIPTION "GEN 3:19"
  ::= { bible 75 }
verse75 OBJECT-TYPE
  SYNTAX OCTET STRING
  ACCESS read-only
  STATUS current
  DESCRIPTION "GEN 3:20"
  ::= { bible 76 }
verse76 OBJECT-TYPE
  SYNTAX OCTET STRING
  ACCESS read-only
  STATUS current
  DESCRIPTION "GEN 3:21"
  ::= { bible 77 }
verse77 OBJECT-TYPE
  SYNTAX OCTET STRING
  ACCESS read-only
  STATUS current
  DESCRIPTION "GEN 3:22"
  ::= { bible 78 }
verse78 OBJECT-TYPE
  SYNTAX OCTET STRING
  ACCESS read-only
  STATUS current
  DESCRIPTION "GEN 3:23"
  ::= { bible 79 }
verse79 OBJECT-TYPE
  SYNTAX OCTET STRING
  ACCESS read-only
  STATUS current
  DESCRIPTION "GEN 3:24"
  ::= { bible 80 }
verse80 OBJECT-TYPE
  SYNTAX OCTET STRING
  ACCESS read-only
  STATUS current
  DESCRIPTION "GEN 4:1"
  ::= { bible 81 }
verse81 OBJECT-TYPE
  SYNTAX OCTET STRING
  ACCESS read-only
  STATUS current
  DESCRIPTION "GEN 4:2"
  ::= { bible 82 }
verse82 OBJECT-TYPE
  SYNTAX OCTET STRING
  ACCESS read-only
  STATUS current
  DESCRIPTION "GEN 4:3"
  ::= { bible 83 }
verse83 OBJECT-TYPE
  SYNTAX OCTET STRING
  ACCESS read-only
  STATUS current
  DESCRIPTION "GEN 4:4"
  ::= { bible 84 }
verse84 OBJECT-TYPE
  SYNTAX OCTET STRING
  ACCESS read-only
  STATUS current
  DESCRIPTION "GEN 4:5"
  ::= { bible 85 }
verse85 OBJECT-TYPE
  SYNTAX OCTET STRING
  ACCESS read-only
  STATUS current
  DESCRIPTION "GEN 4:6"
  ::= { bible 86 }
verse86 OBJECT-TYPE
  SYNTAX OCTET STRING
  ACCESS read-only
  STATUS current
  DESCRIPTION "GEN 4:7"
  ::= { bible 87 }
verse87 OBJECT-TYPE
  SYNTAX OCTET STRING
  ACCESS read-only
  STATUS current
  DESCRIPTION "GEN 4:8"
  ::= { bible 88 }
verse88 OBJECT-TYPE
  SYNTAX OCTET STRING
  ACCESS read-only
  STATUS current
  DESCRIPTION "GEN 4:9"
  ::= { bible 89 }
verse89 OBJECT-TYPE
  SYNTAX OCTET STRING
  ACCESS read-only
  STATUS current
  DESCRIPTION "GEN 4:10"
  ::= { bible 90 }
verse90 OBJECT-TYPE
  SYNTAX OCTET STRING
  ACCESS read-only
  STATUS current
  DESCRIPTION "GEN 4:11"
  ::= { bible 91 }
verse91 OBJECT-TYPE
  SYNTAX OCTET STRING
  ACCESS read-only
  STATUS current
  DESCRIPTION "GEN 4:12"
  ::= { bible 92 }
verse92 OBJECT-TYPE
  SYNTAX OCTET STRING
  ACCESS read-only
  STATUS current
  DESCRIPTION "GEN 4:13"
  ::= { bible 93 }
verse93 OBJECT-TYPE
  SYNTAX OCTET STRING
  ACCESS read-only
  STATUS current
  DESCRIPTION "GEN 4:14"
  ::= { bible 94 }
verse94 OBJECT-TYPE
  SYNTAX OCTET STRING
  ACCESS read-only
  STATUS current
  DESCRIPTION "GEN 4:15"
  ::= { bible 95 }
verse95 OBJECT-TYPE
  SYNTAX OCTET STRING
  ACCESS read-only
  STATUS current
  DESCRIPTION "GEN 4:16"
  ::= { bible 96 }
verse96 OBJECT-TYPE
  SYNTAX OCTET STRING
  ACCESS read-only
  STATUS current
  DESCRIPTION "GEN 4:17"
  ::= { bible 97 }
verse97 OBJECT-TYPE
  SYNTAX OCTET STRING
  ACCESS read-only
  STATUS current
  DESCRIPTION "GEN 4:18"
  ::= { bible 98 }
verse98 OBJECT-TYPE
  SYNTAX OCTET STRING
  ACCESS read-only
  STATUS current
  DESCRIPTION "GEN 4:19"
  ::= { bible 99 }
verse99 OBJECT-TYPE
  SYNTAX OCTET STRING
  ACCESS read-only
  STATUS current
  DESCRIPTION "GEN 4:20"
  ::= { bible 100 }
END
